module iana-igp-flooding-topo-algo {
  yang-version 1.1;
  namespace "urn:ietf:params:xml:ns:yang:"
          + "iana-igp-flooding-topo-algo";
  prefix iana-igp-flood-algo;

  organization
    "Internet Assigned Numbers Authority (IANA)";
  contact
    "Internet Assigned Numbers Authority

     ICANN
     12025 Waterfront Drive, Suite 300
     Los Angeles, CA 90094-2536
     United States of America

     Tel:    +1 310 301 5800
     <mailto:iana@iana.org>";
  description
    "This YANG module defines the identities for IGP Algorithms
     for Computing Flooding Topologies.

     This YANG module is maintained by IANA and reflects the
     'IGP Flooding Reduction Algorithm' registry.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This initial version of this YANG module is part of RFC XXXX
     (https://www.rfc-editor.org/info/rfcXXXX); see the RFC itself
     for full legal notices.

     The latest version of this YANG module is available at
     https://www.iana.org/assignments/yang-parameters.";

  revision 2026-08-13 {
    description
      "Initial version";
    reference
      "RFC 9667: Dynamic Flooding on Dense Graphs";
  }

  typedef igp-flooding-topo-algo {
    type enumeration {
      enum reserved-centralized-mode {
        value 0;
        description
          "Reserved - Centralized mode.";
        reference
          "RFC 9667: Dynamic Flooding on Dense Graphs";
      }
      enum reserved-first-private-algo {
        value 128;
        description
          "Reserved - First private flooding reduction algorithm.";
        reference
          "RFC 9667: Dynamic Flooding on Dense Graphs";
      }
      enum reserved-last-private-algo {
        value 254;
        description
          "Reserved - Last private flooding reduction algorithm.";
        reference
          "RFC 9667: Dynamic Flooding on Dense Graphs";
      }
      enum reserved-last-algo {
        value 255;
        description
          "Reserved - Last alogorithm.";
        reference
          "RFC 9667: Dynamic Flooding on Dense Graphs";
      }
    }
    description
      "IGP algorithms for computing flooding topologies
       Algorithms are defined in the 'IGP Algorithm
       Type for Computing Flooding Topology' in the 'Interior
       Gateway Protocol (IGP) Parameters' registry group.";
    reference
      "RFC 9667: Dynamic Flooding on Dense Graphs";
  }
}
