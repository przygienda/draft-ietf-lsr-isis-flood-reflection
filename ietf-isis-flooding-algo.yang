module ietf-isis-flooding-algo {
  yang-version 1.1;
  namespace "urn:ietf:params:xml:ns:yang:"
          + "ietf-isis-flooding-algo";
  prefix isis-flood-algo;

  import ietf-routing {
    prefix rt;
    reference
      "RFC 8349: A YANG Data Model for Routing Management
                 (NMDA Version)";
  }
  import ietf-isis {
    prefix isis;
    reference
      "RFC 9130: YANG Data Model for the IS-IS Protocol";
  }
  import iana-igp-flooding-algo {
    prefix iana-igp-flooding-algo;
    reference
      "RFC XXXX: Flooding Reduction Algorithms Framework";
  }

  organization
    "IETF Link State Routing (LSR) Working Group";
  contact
    "WG Web:   <https://datatracker.ietf.org/wg/lsr/>
     WG List:  <mailto:lsr@ietf.org>

     Author:   Acee Lindem
               <mailto:acee.ietf@gmail.com>";
  description
    "This YANG module defines the operational state for
     the flooding reduction algorithm in IS-IS as defined
     in RFC XXXX.

     Copyright (c) 2026 IETF Trust and the persons identified as
     authors of the code.  All rights reserved.
     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-02-10 {
    description
      "Initial version";
    reference
      "RFC XXXX: Flooding Reduction Algorithms Framework";
  }
  
  /*
   * IS-IS Flooding Reduction Algorithm configuration
   */
  grouping flooding-reduction-algo-config {
    description
      "Grouping for IS-IS flooding algorithm router
       configuration.";
    container flooding-reduction-algo {
      description
        "IS-IS Level-1 flooding algorithm routing configuration.
         This containers includes configuration related to the the
         active flooding reduction algorithm.";
      leaf flooding-reduction-algo {
        type identityref {
          base iana-igp-flooding-algo:flooding-reduction-algo;
         }
        description
          "Specifies the active flooding reduction algorithm
           in for IS-IS Level 1.
           RFC XXXX: Flooding Reduction Algorithms Framework";
        }
     }
  }  

 augment "/rt:routing/"
        + "rt:control-plane-protocols/rt:control-plane-protocol"
        + "/isis:isis" {
    when "/rt:routing/rt:control-plane-protocols/"
       + "rt:control-plane-protocol/rt:type = 'isis:isis'" {
      description
        "This augment IS-IS routing protocol when used";
    }
    description
      "This augments IS-IS with flooding reduction algorithm
       configuration.";
    container level-1 {
      uses flooding-reduction-algo-config;
      description
        "IS-IS Level-1 Flooding Reduction Algorithm 
         configuration.";
    }  
    container level-2 {
      uses flooding-reduction-algo-config;
      description
        "IS-IS Level-2 Flooding Reduction Algorithm 
         configuration.";
    }  
  }

  /*
   * IS-IS Flooding Reduction Algorithm Router Capabilities
   */
  grouping router-flooding-algorithm-tlv {
    description
      "Grouping for IS-IS router flooding algorithm capabilities
       TLV types.";
    reference
      "RFC 7981: IS-IS Extensions for Advertising Router
                 Information
       RFC XXXX: Flooding Reduction Algorithms Framework";
                                                      
    container router-flooding-algo-tlv {
      description
        "IS-IS Router Flooding Algorithm TLV.";
      leaf active-flooding-algo {
        type identityref {
          base iana-igp-flooding-algo:flooding-reduction-algo;
        }
        description
          "Flooding reduction algorithm active in the
          IS-IS routing domain";
        reference
          "RFC 7981: IS-IS Extensions for Advertising Router
                     Information
           RFC XXXX: Flooding Reduction Algorithms Framework";
      }
    }
  }
  augment "/rt:routing/"
        + "rt:control-plane-protocols/rt:control-plane-protocol"
        + "/isis:isis/isis:database/isis:levels/isis:lsp"
        + "/isis:router-capabilities" {
    when "/rt:routing/rt:control-plane-protocols/"
       + "rt:control-plane-protocol/"
       + "rt:type = 'isis:isis'" {
      description
        "This augment IS-IS routing protocol when used";
    }
    description
      "This augments IS-IS protocol LSDB router capability.";
    uses router-flooding-algorithm-tlv;
  }
}
