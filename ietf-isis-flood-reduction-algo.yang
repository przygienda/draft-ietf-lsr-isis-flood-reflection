module ietf-isis-flood-reduction-algo {
  yang-version 1.1;
  namespace "urn:ietf:params:xml:ns:yang:"
          + "ietf-isis-flood-reduction-algo";
  prefix isis-flood-reduction-algo;

  import ietf-routing {
    prefix rt;
    reference
      "RFC 8349: A YANG Data Model for Routing Management
                 (NMDA Version)";
  }
  import ietf-isis {
    prefix isis;
    reference
      "RFC 9130: YANG Data Model for the IS-IS Protocol";
  }
  import iana-igp-flooding-topo-algo {
    prefix iana-igp-flood-algo;
    reference
      "RFC 9667: Dynamic Flooding on Dense Graphs";
  }

  organization
    "IETF Link State Routing (LSR) Working Group";
  contact
    "WG Web:   <https://datatracker.ietf.org/wg/lsr/>
     WG List:  <mailto:lsr@ietf.org>

     Author:   Acee Lindem
               <mailto:acee.ietf@gmail.com>";
  description
    "This YANG module defines the operational state for
     the flood reduction algorithm in IS-IS as defined
     in RFC XXXX.

     Copyright (c) 2026 IETF Trust and the persons identified as
     authors of the code.  All rights reserved.
     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-02-10 {
    description
      "Initial version";
    reference
      "RFC XXXX: IGP Flooding Reduction Algorithms Framework";
  }

  /*
   * IS-IS Flood Reduction Algorithm configuration
   */

  grouping flood-reduction-algo-config {
    description
      "Grouping for IS-IS flood reduction algorithm router
       configuration.";
    container flood-reduction-algo {
      description
        "IS-IS Level-1 flood reduction algorithm routing
         configuration. This containers includes configuration
         related to the the active flood reduction algorithm.";
      leaf flood-reduction-algo {
        type iana-igp-flood-algo:igp-flooding-topo-algo;
        description
          "Specifies the active flood reduction algorithm
           in for IS-IS Level 1.
           RFC XXXX: IGP Flooding Reduction Algorithms Framework";
      }
    }
  }

  augment "/rt:routing/"
        + "rt:control-plane-protocols/rt:control-plane-protocol"
        + "/isis:isis" {
    when "/rt:routing/rt:control-plane-protocols/"
       + "rt:control-plane-protocol/rt:type = 'isis:isis'" {
      description
        "This augment IS-IS routing protocol when used";
    }
    description
      "This augments IS-IS with flood reduction algorithm
       configuration.";
    container level-1 {
      uses flood-reduction-algo-config;
      description
        "IS-IS Level-1 Flood Reduction Algorithm
         configuration.";
    }
    container level-2 {
      uses flood-reduction-algo-config;
      description
        "IS-IS Level-2 Flood Reduction Algorithm
         configuration.";
    }
  }

  /*
   * IS-IS Flood Reduction Algorithm Router Capabilities
   */

  grouping flood-reduction-algorithm-tlv {
    description
      "Grouping for IS-IS flooding reduction algorithm
       TLV types.";
    reference
      "RFC 7981: IS-IS Extensions for Advertising Router
                 Information
       RFC XXXX: Flooding Reduction Algorithms Framework";
    container flood-reduction-algo-tlv {
      description
        "IS-IS Router Flooding Algorithm TLV.";
      leaf flood-reduction-algo {
        type iana-igp-flood-algo:igp-flooding-topo-algo;
        description
          "Flood reduction algorithm active in the
           IS-IS routing domain";
        reference
          "RFC 7981: IS-IS Extensions for Advertising Router
                     Information
           RFC XXXX: Flooding Reduction Algorithms Framework";
      }
    }
  }

  augment "/rt:routing/"
        + "rt:control-plane-protocols/rt:control-plane-protocol"
        + "/isis:isis/isis:database/isis:levels/isis:lsp"
        + "/isis:router-capabilities" {
    when "/rt:routing/rt:control-plane-protocols/"
       + "rt:control-plane-protocol/"
       + "rt:type = 'isis:isis'" {
      description
        "This augment IS-IS routing protocol when used";
    }
    description
      "This augments IS-IS protocol LSDB router capability.";
    uses flood-reduction-algorithm-tlv;
  }
}
